(defun c:HEX_PYRAMID_PROJECTION (/ )
  (command "_.UNITS" 2 3 1 0 0 "N")
  (command "_.-LAYER" "M" "Object Lines" "C" "7" "" "LT" "Continuous" "" "LW" "0.35" "" "")
  (command "_.-LAYER" "M" "Hidden Lines" "C" "1" "" "LT" "Hidden" "" "LW" "0.18" "" "")
  (command "_.-LAYER" "M" "Construction Lines" "C" "8" "" "LT" "Continuous" "" "LW" "0.09" "" "")
  (command "_.-LAYER" "M" "Centre Lines" "C" "3" "" "LT" "Center" "" "LW" "0.13" "" "")
  (command "_.-LAYER" "M" "Dimensions" "C" "5" "" "LT" "Continuous" "" "LW" "0.13" "" "")
  (command "_.-LAYER" "S" "Construction Lines" "")
  (command "_.LINE" (list 40.000000 90.000000 0) (list 170.000000 90.000000 0) "")
  (command "_.-LAYER" "S" "Construction Lines" "")
  (command "_.TEXT" (list 42.000000 93.000000 0) 3 0 "X-Y")
  (command "_.-LAYER" "S" "Construction Lines" "")
  (command "_.LINE" (list 120.000000 90.000000 0) (list 120.000000 42.500000 0) "")
  (command "_.-LAYER" "S" "Construction Lines" "")
  (command "_.LINE" (list 120.000000 90.000000 0) (list 120.000000 17.500000 0) "")
  (command "_.-LAYER" "S" "Construction Lines" "")
  (command "_.LINE" (list 130.825318 108.750000 0) (list 130.825318 5.000000 0) "")
  (command "_.-LAYER" "S" "Construction Lines" "")
  (command "_.LINE" (list 141.650635 127.500000 0) (list 141.650635 17.500000 0) "")
  (command "_.-LAYER" "S" "Construction Lines" "")
  (command "_.LINE" (list 141.650635 127.500000 0) (list 141.650635 42.500000 0) "")
  (command "_.-LAYER" "S" "Construction Lines" "")
  (command "_.LINE" (list 130.825318 108.750000 0) (list 130.825318 55.000000 0) "")
  (command "_.-LAYER" "S" "Construction Lines" "")
  (command "_.LINE" (list 87.524047 133.750000 0) (list 87.524047 30.000000 0) "")
  (command "_.-LAYER" "S" "Hidden Lines" "")
  (command "_.LINE" (list 120.000000 90.000000 0) (list 120.000000 90.000000 0) "")
  (command "_.-LAYER" "S" "Hidden Lines" "")
  (command "_.LINE" (list 141.650635 127.500000 0) (list 141.650635 127.500000 0) "")
  (command "_.-LAYER" "S" "Hidden Lines" "")
  (command "_.LINE" (list 141.650635 127.500000 0) (list 130.825318 108.750000 0) "")
  (command "_.-LAYER" "S" "Hidden Lines" "")
  (command "_.LINE" (list 130.825318 108.750000 0) (list 120.000000 90.000000 0) "")
  (command "_.-LAYER" "S" "Hidden Lines" "")
  (command "_.LINE" (list 120.000000 90.000000 0) (list 87.524047 133.750000 0) "")
  (command "_.-LAYER" "S" "Hidden Lines" "")
  (command "_.LINE" (list 141.650635 127.500000 0) (list 87.524047 133.750000 0) "")
  (command "_.-LAYER" "S" "Hidden Lines" "")
  (command "_.LINE" (list 130.825318 108.750000 0) (list 87.524047 133.750000 0) "")
  (command "_.-LAYER" "S" "Object Lines" "")
  (command "_.LINE" (list 120.000000 90.000000 0) (list 130.825318 108.750000 0) "")
  (command "_.-LAYER" "S" "Object Lines" "")
  (command "_.LINE" (list 130.825318 108.750000 0) (list 141.650635 127.500000 0) "")
  (command "_.-LAYER" "S" "Object Lines" "")
  (command "_.LINE" (list 120.000000 90.000000 0) (list 87.524047 133.750000 0) "")
  (command "_.-LAYER" "S" "Object Lines" "")
  (command "_.LINE" (list 130.825318 108.750000 0) (list 87.524047 133.750000 0) "")
  (command "_.-LAYER" "S" "Object Lines" "")
  (command "_.LINE" (list 141.650635 127.500000 0) (list 87.524047 133.750000 0) "")
  (command "_.-LAYER" "S" "Hidden Lines" "")
  (command "_.LINE" (list 120.000000 42.500000 0) (list 120.000000 17.500000 0) "")
  (command "_.-LAYER" "S" "Hidden Lines" "")
  (command "_.LINE" (list 120.000000 17.500000 0) (list 130.825318 5.000000 0) "")
  (command "_.-LAYER" "S" "Hidden Lines" "")
  (command "_.LINE" (list 130.825318 55.000000 0) (list 120.000000 42.500000 0) "")
  (command "_.-LAYER" "S" "Hidden Lines" "")
  (command "_.LINE" (list 120.000000 42.500000 0) (list 87.524047 30.000000 0) "")
  (command "_.-LAYER" "S" "Hidden Lines" "")
  (command "_.LINE" (list 120.000000 17.500000 0) (list 87.524047 30.000000 0) "")
  (command "_.-LAYER" "S" "Object Lines" "")
  (command "_.LINE" (list 130.825318 5.000000 0) (list 141.650635 17.500000 0) "")
  (command "_.-LAYER" "S" "Object Lines" "")
  (command "_.LINE" (list 141.650635 17.500000 0) (list 141.650635 42.500000 0) "")
  (command "_.-LAYER" "S" "Object Lines" "")
  (command "_.LINE" (list 141.650635 42.500000 0) (list 130.825318 55.000000 0) "")
  (command "_.-LAYER" "S" "Object Lines" "")
  (command "_.LINE" (list 130.825318 5.000000 0) (list 87.524047 30.000000 0) "")
  (command "_.-LAYER" "S" "Object Lines" "")
  (command "_.LINE" (list 141.650635 17.500000 0) (list 87.524047 30.000000 0) "")
  (command "_.-LAYER" "S" "Object Lines" "")
  (command "_.LINE" (list 141.650635 42.500000 0) (list 87.524047 30.000000 0) "")
  (command "_.-LAYER" "S" "Object Lines" "")
  (command "_.LINE" (list 130.825318 55.000000 0) (list 87.524047 30.000000 0) "")
  (command "_.-LAYER" "S" "Centre Lines" "")
  (command "_.LINE" (list 130.825318 108.750000 0) (list 87.524047 133.750000 0) "")
  (command "_.-LAYER" "S" "Centre Lines" "")
  (command "_.LINE" (list 130.825318 30.000000 0) (list 87.524047 30.000000 0) "")
  (command "_.-LAYER" "S" "Dimensions" "")
  (command "_.TEXT" (list 121.000000 91.000000 0) 2.5 0 "a'")
  (command "_.-LAYER" "S" "Dimensions" "")
  (command "_.TEXT" (list 121.000000 43.500000 0) 2.5 0 "a")
  (command "_.-LAYER" "S" "Dimensions" "")
  (command "_.TEXT" (list 121.000000 91.000000 0) 2.5 0 "b'")
  (command "_.-LAYER" "S" "Dimensions" "")
  (command "_.TEXT" (list 121.000000 18.500000 0) 2.5 0 "b")
  (command "_.-LAYER" "S" "Dimensions" "")
  (command "_.TEXT" (list 131.825318 109.750000 0) 2.5 0 "c'")
  (command "_.-LAYER" "S" "Dimensions" "")
  (command "_.TEXT" (list 131.825318 6.000000 0) 2.5 0 "c")
  (command "_.-LAYER" "S" "Dimensions" "")
  (command "_.TEXT" (list 142.650635 128.500000 0) 2.5 0 "d'")
  (command "_.-LAYER" "S" "Dimensions" "")
  (command "_.TEXT" (list 142.650635 18.500000 0) 2.5 0 "d")
  (command "_.-LAYER" "S" "Dimensions" "")
  (command "_.TEXT" (list 142.650635 128.500000 0) 2.5 0 "e'")
  (command "_.-LAYER" "S" "Dimensions" "")
  (command "_.TEXT" (list 142.650635 43.500000 0) 2.5 0 "e")
  (command "_.-LAYER" "S" "Dimensions" "")
  (command "_.TEXT" (list 131.825318 109.750000 0) 2.5 0 "f'")
  (command "_.-LAYER" "S" "Dimensions" "")
  (command "_.TEXT" (list 131.825318 56.000000 0) 2.5 0 "f")
  (command "_.-LAYER" "S" "Dimensions" "")
  (command "_.TEXT" (list 88.524047 134.750000 0) 2.5 0 "O'")
  (command "_.-LAYER" "S" "Dimensions" "")
  (command "_.TEXT" (list 88.524047 31.000000 0) 2.5 0 "O")
  (command "_.-LAYER" "S" "Dimensions" "")
  (command "_.TEXT" (list 90.000000 125.000000 0) 4 0 "FINAL FRONT VIEW")
  (command "_.-LAYER" "S" "Dimensions" "")
  (command "_.TEXT" (list 90.000000 -5.000000 0) 4 0 "FINAL TOP VIEW")
  (command "_.-LAYER" "S" "Dimensions" "")
  (command "_.LINE" (list 120.000000 42.500000 0) (list 120.000000 17.500000 0) "")
  (command "_.-LAYER" "S" "Dimensions" "")
  (command "_.TEXT" (list 124.000000 38.500000 0) 3 0 "Base side = 25 mm")
  (command "_.-LAYER" "S" "Dimensions" "")
  (command "_.LINE" (list 130.825318 108.750000 0) (list 87.524047 133.750000 0) "")
  (command "_.-LAYER" "S" "Dimensions" "")
  (command "_.TEXT" (list 109.174682 125.250000 0) 3 0 "Axis = 50 mm")
  (command "_.-LAYER" "S" "Dimensions" "")
  (command "_.LINE" (list 130.825318 108.750000 0) (list 158.825318 108.750000 0) "")
  (command "_.-LAYER" "S" "Dimensions" "")
  (command "_.LINE" (list 130.825318 108.750000 0) (list 106.576606 122.750000 0) "")
  (command "_.-LAYER" "S" "Dimensions" "")
  (command "_.TEXT" (list 110.825318 116.750000 0) 3 0 "30° to H.P.")
  (princ)
)
(c:HEX_PYRAMID_PROJECTION)
